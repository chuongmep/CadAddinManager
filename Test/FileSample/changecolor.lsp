(defun C:choice ()
   (initget 1 "1 2 3")
   (setq COLOR (getkword "\nSelect 1, 2 or 3 \n1. CHANGE COLOR TO RED\n2. CHANGE COLOR TO YELLOW\n3. CHANGE COLOR TO GREEN: "))
   (setq PT1 (getpoint "\nSelect first corner of window: "))
   (setq PT2 (getcorner PT1 "\nSelect opposite corner: "))
   (if (setq SS (ssget "W" PT1 PT2))
      (progn
         (command "change" SS "" "properties" "color" COLOR "")
         (prompt (strcat "\n" (itoa (sslength SS)) " Entities were changed to the COLOR " (nth (atoi COLOR) '(0 "red" "yellow" "green"))))
      )
      (Prompt "\nNo entities select.")
   )
   (princ)
)
